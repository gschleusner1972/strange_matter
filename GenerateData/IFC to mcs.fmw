FME workspace IFC to mcs.fmw

Parameters:
- SourceDataset_REVIT = C:\+HOK\OneDrive - HOK\Downloads 677\Sample_ECS_IFC.ifc   # Source IFC File(s)
- DestDataset_JSON_5 = $(FME_MF_DIR)jsontest\   # Destination JSON (JavaScript Object Notation) File
- DestDataset_JSON_7 = $(FME_MF_DIR)jsontest   # Destination JSON (JavaScript Object Notation) File
- DestDataset_JSON_6 = $(FME_MF_DIR)jsontest   # Destination JSON (JavaScript Object Notation) File
- DestDataset_JSON = $(FME_MF_DIR)jsontest   # Destination JSON (JavaScript Object Notation) File

Readers:
- REVIT_1: REVIT from $(SourceDataset_REVIT)

Writers:
- JSON_1: JSON to $(DestDataset_JSON_5)
- JSON_4: JSON to $(DestDataset_JSON_7)
- JSON_2: JSON to $(DestDataset_JSON)
- JSON_3: JSON to $(DestDataset_JSON_6)

BuildingElementProxy (reader REVIT_1)
    attributes: element_parent_id char(200), element_id char(200), GlobalId char(200), Name char(200), ObjectType char(200), Tag char(200), Constraints.Host char(200), Constraints.Level char(200), Constraints.Moves With Nearby Elements logical, Dimensions.Depth double, Dimensions.Height double, Dimensions.Width double, Dimensions.Volume double, Electrical - Loads.Circuit Number char(200), Electrical - Loads.Panel char(200), Identity Data.Assembly Code char(200), Identity Data.Assembly Description char(200), Identity Data.OmniClass Number char(200), Identity Data.OmniClass Title char(200), Phasing.Phase Created char(200), Pset_BuildingElementProxyCommon.Reference char(200), Pset_SpaceCommon.Reference char(200), Text.Label char(200), Pset_ManufacturerTypeInformation.Manufacturer char(200), Pset_ManufacturerTypeInformation.ModelLabel char(200), Pset_ManufacturerTypeInformation.ModelReference char(200), Pset_ManufacturerTypeInformation.ProductionYear char(200)
    -> UUIDGenerator
Door (reader REVIT_1)
    attributes: element_parent_id char(200), element_id char(200), GlobalId char(200), Name char(200), ObjectType char(200), Tag char(200), OverallHeight double, OverallWidth double, Analytical Properties.Analytic Construction char(200), BaseQuantities.Area double, BaseQuantities.Height double, BaseQuantities.Width double, Constraints.Level char(200), Constraints.Sill Height double, Construction.Function char(200), Construction.Wall Closure char(200), Dimensions.Height char(200), Dimensions.Rail Width - Base double, Dimensions.Rail Width - Top double, Dimensions.Stile Width - Hinge double, Dimensions.Stile Width - Latch double, Dimensions.Thickness char(200), Dimensions.Trim Projection Ext double, Dimensions.Trim Projection Int double, Dimensions.Trim Width double, Dimensions.Width double, Identity Data.Assembly Code char(200), Identity Data.Assembly Description char(200), Identity Data.Mark char(200), Identity Data.OmniClass Number char(200),
      Identity Data.OmniClass Title char(200), Identity Data.Type Mark char(200), Materials and Finishes.Door Material char(200), Materials and Finishes.Frame Material char(200), Other.Head Height double, Other.Trim Width double, Phasing.Phase Created char(200), Pset_DoorCommon.IsExternal logical, Pset_DoorCommon.Reference (utf-8) char(200), Pset_ManufacturerTypeInformation.Manufacturer char(200), Pset_ManufacturerTypeInformation.ModelLabel char(200), Pset_ManufacturerTypeInformation.ModelReference char(200), Pset_ManufacturerTypeInformation.ProductionYear char(200)
    -> UUIDGenerator
Opening (reader REVIT_1)
    attributes: element_parent_id char(200), element_id char(200), GlobalId char(200), Name char(200), ObjectType char(200), Tag char(200), BaseQuantities.Depth double, BaseQuantities.Height double, BaseQuantities.Width double
    -> UUIDGenerator
DistributionPort (reader REVIT_1)
    attributes: element_id char(200), element_parent_id char(200), ControlElementId char(200), GlobalId char(200), Name char(200), FlowDirection char(200), Description char(200)
    -> UUIDGenerator
Project (reader REVIT_1)
    attributes: element_id char(200), Name char(200), LongName char(200), Phase char(200), GlobalId char(200), AreaUnit char(20), LengthUnit char(20), MassUnit char(20), PlaneAngleUnit char(20), PowerUnit char(20), TemperatureUnit char(20), TimeUnit char(20), VolumeUnit char(20)
    -> UUIDGenerator
Slab (reader REVIT_1)
    attributes: element_parent_id char(200), element_id char(200), GlobalId char(200), Name char(200), ObjectType char(200), Tag char(200), OverallHeight double, OverallWidth double, Analytical Properties.Absorptance double, Analytical Properties.Roughness double, BaseQuantities.GrossArea double, BaseQuantities.GrossVolume double, BaseQuantities.Perimeter double, BaseQuantities.Width double, Constraints.Base Level char(200), Constraints.Base Offset From Level double, Constraints.Cutoff Offset double, Constraints.Height Offset From Level double, Constraints.Level char(200), Constraints.Related to Mass logical, Constraints.Room Bounding logical, Construction.Default Thickness double, Construction.Fascia Depth double, Construction.Function char(200), Construction.Maximum Ridge Height double, Construction.Rafter Cut char(200), Construction.Rafter or Truss char(200), Construction.Thickness double, Dimensions.Area double, Dimensions.Perimeter double,
      Dimensions.Slope double, Dimensions.Thickness double, Dimensions.Volume double, Graphics.Coarse Scale Fill Color double, Identity Data.Assembly Code char(200), Identity Data.Assembly Description char(200), Materials and Finishes.Structural Material char(200), Phasing.Phase Created char(200), Pset_RoofCommon.IsExternal logical, Pset_RoofCommon.ProjectedArea double, Pset_RoofCommon.Reference char(200), Pset_RoofCommon.TotalArea double, Pset_SlabCommon.IsExternal logical, Pset_SlabCommon.LoadBearing logical, Pset_SlabCommon.Reference char(200), Pset_ManufacturerTypeInformation.Manufacturer char(200), Pset_ManufacturerTypeInformation.ModelLabel char(200), Pset_ManufacturerTypeInformation.ModelReference char(200), Pset_ManufacturerTypeInformation.ProductionYear char(200)
    -> UUIDGenerator
Space (reader REVIT_1)
    attributes: element_parent_id char(200), element_id char(200), Name char(200), GlobalId char(200), LongName char(200), InteriorOrExteriorSpace char(200), BaseQuantities.GrossFloorArea double, BaseQuantities.GrossPerimeter double, BaseQuantities.GrossVolume double, BaseQuantities.Height double, BaseQuantities.NetFloorArea double, Constraints.Base Offset double, Constraints.Level char(200), Constraints.Limit Offset double, Constraints.Upper Limit char(200), Dimensions.Area double, Dimensions.Computation Height double, Dimensions.Perimeter double, Dimensions.Unbounded Height double, Phasing.Phase (utf-8) char(200), Pset_SpaceCommon.Reference (utf-8) char(200)
    -> UUIDGenerator
Wall (reader REVIT_1)
    attributes: element_parent_id char(200), element_id char(200), GlobalId char(200), Name char(200), ObjectType char(200), Tag char(200), Analytical Properties.Roughness double, Analytical Properties.Absorptance double, BaseQuantities.GrossFootprintArea double, BaseQuantities.GrossSideArea double, BaseQuantities.GrossVolume double, BaseQuantities.Height double, BaseQuantities.Length double, BaseQuantities.Width double, Constraints.Base Constraint char(200), Constraints.Base Extension Distance double, Constraints.Base is Attached logical, Constraints.Base Offset double, Constraints.Location Line char(200), Constraints.Related to Mass logical, Constraints.Room Bounding logical, Constraints.Top Constraint char(200), Constraints.Top Extension Distance double, Constraints.Top is Attached logical, Constraints.Top Offset double, Constraints.Unconnected Height double, Construction.Function char(200), Construction.Width double, Construction.Wrapping at Ends char(200), Construction.Wrapping at Inserts char(200),
      Dimensions.Area double, Dimensions.Length double, Dimensions.Volume double, Graphics.Coarse Scale Fill Color integer, Graphics.Coarse Scale Fill Pattern char(200), Identity Data.Assembly Code char(200), Identity Data.Assembly Description char(200), Materials and Finishes.Structural Material char(200), Phasing.Phase Created char(200), Pset_WallCommon.ExtendToStructure logical, Pset_WallCommon.IsExternal logical, Pset_WallCommon.LoadBearing logical, Pset_WallCommon.Reference char(200), Structural.Enable Analytical Model logical, Structural.Structural logical, Structural.Structural Usage char(200), Pset_ManufacturerTypeInformation.Manufacturer char(200), Pset_ManufacturerTypeInformation.ModelLabel char(200), Pset_ManufacturerTypeInformation.ModelReference char(200), Pset_ManufacturerTypeInformation.ProductionYear char(200)
    -> UUIDGenerator
Window (reader REVIT_1)
    attributes: element_parent_id char(200), element_id char(200), GlobalId char(200), Name char(200), ObjectType char(200), Tag char(200), OverallHeight double, OverallWidth double, Analytical Properties.Analytic Construction char(200), BaseQuantities.Area double, BaseQuantities.Height double, BaseQuantities.Width double, Constraints.Level char(200), Constraints.Sill Height double, Construction.Wall Closure char(200), Dimensions.Default Sill Height double, Dimensions.Height double, Dimensions.Width double, Dimensions.Window Inset double, Identity Data.Assembly Code char(200), Identity Data.Assembly Description char(200), Identity Data.Mark char(200), Identity Data.OmniClass Number char(200), Identity Data.OmniClass Title char(200), Identity Data.Type Mark char(200), Materials and Finishes.Glass Pane Material char(200), Materials and Finishes.Sash Material char(200), Other.Head Height double, Phasing.Phase Created char(200), Pset_WindowCommon.IsExternal logical,
      Pset_WindowCommon.Reference char(200), Pset_ManufacturerTypeInformation.Manufacturer char(200), Pset_ManufacturerTypeInformation.ModelLabel char(200), Pset_ManufacturerTypeInformation.ModelReference char(200), Pset_ManufacturerTypeInformation.ProductionYear char(200)
    -> UUIDGenerator
Building (reader REVIT_1)
    attributes: element_id char(200), element_parent_id char(200), LongName char(200), Name char(200), GlobalId char(200), BuildingAddress.AddressLines{} char(200), BuildingAddress.Country char(200), BuildingAddress.PostalCode char(200), BuildingAddress.Region char(200), BuildingAddress.Town char(200), Identity Data.Author char(200), Identity Data.Building Name char(200), Identity Data.Organization Description char(200), Identity Data.Organization Name char(200), Pset_BuildingCommon.NumberOfStoreys integer
    -> UUIDGenerator
Site (reader REVIT_1)
    attributes: element_id char(200), element_parent_id char(200), Name char(255), ObjectType char(255), RefElevation double, RefLatitude double, RefLongitude double, GlobalId char(200), Dimensions.Projected Area double, Dimensions.Surface Area double, Materials and Finishes.Material char(200), Phasing.Phase Created char(200)
    -> UUIDGenerator
BuildingStorey (reader REVIT_1)
    attributes: element_id char(200), element_parent_id char(200), Elevation double, GlobalId char(200), Name char(200), LongName char(200), Dimensions.Computation Height double, Identity Data.Building Story char(200), Identity Data.Structural char(200), Pset_BuildingStoreyCommon.AboveGround char(200)
    -> UUIDGenerator
UUIDGenerator
    UUID_ATTR = _uuid
    UUID_FORMAT = UUID_ONLY
    -> BaseComponent
BaseComponent: AttributeManager
    ATTR_TABLE:
      SET_TO component_version (uint64) = 00001
      SET_TO entity_guid (varchar(200))
      SET_TO component_guid (buffer) = @Value(_uuid)
      SET_TO name (varchar(200)) = @Value(Name)
      SET_TO context (buffer) = hok.com/projects/123...
      SET_TO author (buffer) = hok
      SET_TO source_data (varchar(200)) = $(SourceDataset_REVIT)
      SET_TO source_data_id (varchar(200)) = @UUID()
      SET_TO component_type (varchar(200))
      SET_TO component_type_reference (buffer) = https://buildingsmart.com/componentifc5010
      SET_TO version (varchar(200)) = @Evaluate(@int(@rand()*5))
      SET_TO status (buffer) = WIP
      SET_TO active (uint64) = 1
      SET_TO author_software (buffer) = Revit 2024
      SET_TO hash1 (varchar(200)) = @UUID()
      SET_TO payload_data_type (varchar(200))
      SET_TO date_created (varchar(200)) = @DateTimeNow()
    -> GeometryFilter
    -> TestFilter
    -> Classification (writer JSON_1)
GeometryFilter
    FILTER_MODE = SIMPLE
    FILTER_MULTI = FILTER_TYPES]"Area Line Null Point PointCloud Raster Solid Surface Text VoxelGrid"]FME_CONTROLLER_QUERY_FILE]]FME_CONTROLLER_CHOICE]Simple
    Surface -> GeometryExtractor
    Surface -> CoordinateExtractor
    Solid -> CoordinateExtractor
    Solid -> GeometryExtractor
GeometryExtractor
    ATTR = _geometry
    JSON_MAX_DIGITS = 7
    KIND_LONG = GeoJSON
    REMOVE_GEOMETRY = No
    -> NewFeatureType00 (writer JSON_2)
Note: Geometry
NewFeatureType00 (writer JSON_2)
    attributes: component_version string, entity_guid string, component_guid string, name string, context string, author string, source_data string, source_data_id string, component_type string, component_type_reference string, version string, status string, active string, author_software string, hash1 string, payload_data_type string, date_created string, _geometry string
CoordinateExtractor
    IND = 0
    MODE = Specify Coordinate
    X_ATTR = _x
    Y_ATTR = _y
    Z_ATTR = _z
    Z_DEFAULT = 0
    -> NewFeatureType (writer JSON_3)
Note: Location
NewFeatureType (writer JSON_3)
    attributes: component_version string, entity_guid string, component_guid string, name string, context string, author string, source_data string, source_data_id string, component_type string, component_type_reference string, version string, status string, active string, author_software string, hash1 string, payload_data_type string, date_created string, _x float, _y float, _z float
Note: Classification
Classification (writer JSON_1)
    attributes: component_version string, entity_guid string, component_guid string, name string, context string, author string, source_data string, source_data_id string, component_type string, component_type_reference string, version string, status string, active string, author_software string, hash1 string, payload_data_type string, date_created string, classification string
TestFilter
    DEFAULT_VALUE = <UNFILTERED>
    PASSED_TEST_GROUP_OUTPUT = ALL
    TEST_LIST = "BOOL_OP,OR,COMPOSITE_TEST,""""""1"""""",TEST_CLAUSE,TEST @Value(fme_feature_type) = BuildingElementProxy",@Value(fme_feature_type) = BEP
    @Value(fme_feature_type) = BEP -> properties (writer JSON_4)
    <UNFILTERED> -> properties (writer JSON_4)
Note: PSET
properties (writer JSON_4)
    attributes: component_version string, entity_guid string, component_guid string, name string, context string, author string, source_data string, source_data_id string, component_type string, component_type_reference string, version string, status string, active string, author_software string, hash1 string, payload_data_type string, date_created string, element_parent_id string, element_id string, GlobalId string, Name string, ObjectType string, Tag string, Constraints.Host string, Constraints.Level string, Constraints.Moves With Nearby Elements boolean, Dimensions.Depth float, Dimensions.Height float, Dimensions.Width float, Dimensions.Volume float,
      Electrical - Loads.Circuit Number string, Electrical - Loads.Panel string, Identity Data.Assembly Code string, Identity Data.Assembly Description string, Identity Data.OmniClass Number string, Identity Data.OmniClass Title string, Phasing.Phase Created string, Pset_BuildingElementProxyCommon.Reference string, Pset_SpaceCommon.Reference string, Text.Label string, Pset_ManufacturerTypeInformation.Manufacturer string, Pset_ManufacturerTypeInformation.ModelLabel string, Pset_ManufacturerTypeInformation.ModelReference string, Pset_ManufacturerTypeInformation.ProductionYear string, multi_reader_full_id int, multi_reader_id int, multi_reader_keyword string, multi_reader_type string, LongName string, Dimensions.Computation Height float, ControlElementId string, FlowDirection string, Description string, OverallHeight float, OverallWidth float, Analytical Properties.Analytic Construction string, BaseQuantities.Area float, BaseQuantities.Height float, BaseQuantities.Width float, Constraints.Sill Height float,
      Construction.Function string, Construction.Wall Closure string, Dimensions.Rail Width - Base float, Dimensions.Rail Width - Top float, Dimensions.Stile Width - Hinge float, Dimensions.Stile Width - Latch float, Dimensions.Thickness string, Dimensions.Trim Projection Ext float, Dimensions.Trim Projection Int float, Dimensions.Trim Width float, Identity Data.Mark string, Identity Data.Type Mark string, Materials and Finishes.Door Material string, Materials and Finishes.Frame Material string, Other.Head Height float, Other.Trim Width float, Pset_DoorCommon.IsExternal boolean, Pset_DoorCommon.Reference (utf-8) string, BaseQuantities.Depth float, Phase string, AreaUnit string, LengthUnit string, MassUnit string, PlaneAngleUnit string, PowerUnit string, TemperatureUnit string, TimeUnit string, VolumeUnit string, Analytical Properties.Absorptance float, Analytical Properties.Roughness float,
      BaseQuantities.GrossArea float, BaseQuantities.GrossVolume float, BaseQuantities.Perimeter float, Constraints.Base Level string, Constraints.Base Offset From Level float, Constraints.Cutoff Offset float, Constraints.Height Offset From Level float, Constraints.Related to Mass boolean, Constraints.Room Bounding boolean, Construction.Default Thickness float, Construction.Fascia Depth float, Construction.Maximum Ridge Height float, Construction.Rafter Cut string, Construction.Rafter or Truss string, Construction.Thickness float, Dimensions.Area float, Dimensions.Perimeter float, Dimensions.Slope float, Graphics.Coarse Scale Fill Color int, Materials and Finishes.Structural Material string, Pset_RoofCommon.IsExternal boolean, Pset_RoofCommon.ProjectedArea float, Pset_RoofCommon.Reference string, Pset_RoofCommon.TotalArea float, Pset_SlabCommon.IsExternal boolean, Pset_SlabCommon.LoadBearing boolean, Pset_SlabCommon.Reference string, InteriorOrExteriorSpace string, BaseQuantities.GrossFloorArea float, BaseQuantities.GrossPerimeter float,
      BaseQuantities.NetFloorArea float, Constraints.Base Offset float, Constraints.Limit Offset float, Constraints.Upper Limit string, Dimensions.Unbounded Height float, Phasing.Phase (utf-8) string, Pset_SpaceCommon.Reference (utf-8) string, BaseQuantities.GrossFootprintArea float, BaseQuantities.GrossSideArea float, BaseQuantities.Length float, Constraints.Base Constraint string, Constraints.Base Extension Distance float, Constraints.Base is Attached boolean, Constraints.Location Line string, Constraints.Top Constraint string, Constraints.Top Extension Distance float, Constraints.Top is Attached boolean, Constraints.Top Offset float, Constraints.Unconnected Height float, Construction.Width float, Construction.Wrapping at Ends string, Construction.Wrapping at Inserts string, Dimensions.Length float, Graphics.Coarse Scale Fill Pattern string, Pset_WallCommon.ExtendToStructure boolean, Pset_WallCommon.IsExternal boolean, Pset_WallCommon.LoadBearing boolean, Pset_WallCommon.Reference string, Structural.Enable Analytical Model boolean, Structural.Structural boolean,
      Structural.Structural Usage string, Dimensions.Default Sill Height float, Dimensions.Window Inset float, Materials and Finishes.Glass Pane Material string, Materials and Finishes.Sash Material string, Pset_WindowCommon.IsExternal boolean, Pset_WindowCommon.Reference string, _uuid string, Elevation float, Identity Data.Building Story string, Identity Data.Structural string, Pset_BuildingStoreyCommon.AboveGround string, RefElevation float, RefLatitude float, RefLongitude float, Dimensions.Projected Area float, Dimensions.Surface Area float, Materials and Finishes.Material string, BuildingAddress.AddressLines{} string, BuildingAddress.Country string, BuildingAddress.PostalCode string, BuildingAddress.Region string, BuildingAddress.Town string, Identity Data.Author string, Identity Data.Building Name string, Identity Data.Organization Description string, Identity Data.Organization Name string, Pset_BuildingCommon.NumberOfStoreys int
